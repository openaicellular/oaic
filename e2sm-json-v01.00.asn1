-- **************************************************************
-- E2SM-JSON
-- Information Element Definitions
-- Based on NexRAN from POWDER
--
-- **************************************************************

-- Control messages:
-- string payload

-- Report/indication messages
-- string payload

E2SM-JSON-IEs {
iso(1) identified-organization(3) dod(6) internet(1) private(4) enterprise(1) 53148 e2(1) version1 (1) e2sm(2) e2sm-JSON-IEs (100)}

DEFINITIONS AUTOMATIC TAGS ::=

BEGIN

-- **************************************************************
-- Message IEs
-- **************************************************************

StringPayload ::= OCTET STRING

-- **************************************************************
-- RAN Function Description
-- **************************************************************

RANfunction-Name ::= SEQUENCE {
    ranFunction-ShortName   PrintableString(SIZE(1..150,...)),
    ranFunction-E2SM-OID    PrintableString(SIZE(1..1000,...)),
    ranFunction-Description PrintableString(SIZE(1..150,...)),
    ranFunction-Instance    INTEGER OPTIONAL,
    ...
}

RANfunction-Description ::= SEQUENCE {
    ranFunction-Name RANfunction-Name,
    ...
}

-- **************************************************************
-- Control Header contents
-- **************************************************************

E2SM-JSON-ControlMessage-Id ::= ENUMERATED {
    stringPayload,
    ...
}

E2SM-JSON-ControlHeader ::= CHOICE {
    controlHeaderFormat1 E2SM-JSON-ControlHeader-Format1,
    ...
}

E2SM-JSON-ControlHeader-Format1 ::= SEQUENCE {
    controlMessageId E2SM-JSON-ControlMessage-Id,
    ...
}

-- **************************************************************
-- Control Message contents
-- **************************************************************

E2SM-JSON-ControlMessage ::= SEQUENCE {
    stringPayload StringPayload
}

-- ***************************************************
-- Control Outcome contents
-- ***************************************************

E2SM-JSON-ControlOutcome ::= CHOICE {
    controlOutcomeFormat1 E2SM-JSON-ControlOutcome-Format1,
    ...
}

E2SM-JSON-ControlOutcome-Format1 ::= CHOICE {
    stringPayload StringPayload,
    ...
}


E2SM-JSON-EventTriggerDefinition ::= CHOICE {
    periodDefinition E2SM-JSON-EventTriggerDefinition-Period,
    ...
}

E2SM-JSON-EventTriggerDefinition-Period ::= SEQUENCE {
    period INTEGER (10..10240),
    ...
}

E2SM-JSON-ActionType ::= ENUMERATED {
    stringPayload,
    ...
}

E2SM-JSON-ActionDefinition ::= SEQUENCE {
    actionType E2SM-JSON-ActionType,
    ...
}

-- E2SM-JSON-IndicationType ::= ENUMERATED {
--     stringPayload,
--     ...
-- }

E2SM-JSON-IndicationHeader ::= SEQUENCE {
    stringPayload StringPayload
}

E2SM-JSON-IndicationMessage ::= SEQUENCE {
    stringPayload StringPayload
}

END
